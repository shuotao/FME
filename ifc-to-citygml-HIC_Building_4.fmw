FME workspace ifc-to-citygml-HIC_Building_4.fmw

Parameters:
- SourceDataset_IFC = $(FME_MF_DIR)HIC_Building_4.ifc   # Source Industry Foundation Class (IFC) File(s)
- DestDataset_CITYGML = $(FME_MF_DIR)HIC_Building_4.gml   # Destination CityGML Document
- DIRNAME = D:\Users\09014\Desktop\MLIT_IFCtoCityGMLonFME\羽田関連   # OutputFolder Select an output folder
- SourceDataset_IFC_4 = $(FME_MF_DIR)HIC_Building_4.ifc   # Source Industry Foundation Class (IFC) File(s)

Readers:
- IFC_1: IFC from $(SourceDataset_IFC)
- IFC_2: IFC from $(SourceDataset_IFC)
- IFC_3: IFC from $(SourceDataset_IFC_4)

Writers:
- CITYGML_1: CITYGML to $(DestDataset_CITYGML)

IfcFurnishingElement (reader IFC_3)
    attributes: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
IfcWallStandardCase (reader IFC_3)
    attributes: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
PropertySetDefinition (reader IFC_3)
    attributes: ifc_properties{}.data_type string, ifc_properties{}.name string, ifc_properties{}.property_type string, ifc_property_set_name string
QuantitySetDefinition (reader IFC_3)
    attributes: ifc_quantities{}.name string, ifc_quantities{}.type string, ifc_quantity_set_name string
IfcBuilding (reader IFC_3)
    attributes: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
IfcBuildingStorey (reader IFC_3)
    attributes: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
IfcCurtainWall (reader IFC_3)
    attributes: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
IfcDoor (reader IFC_3)
    attributes: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
IfcFooting (reader IFC_3)
    attributes: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
IfcOpeningElement (reader IFC_3)
    attributes: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
IfcProject (reader IFC_3)
    attributes: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
IfcSite (reader IFC_3)
    attributes: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
IfcSlab (reader IFC_3)
    attributes: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
IfcSpace (reader IFC_3)
    attributes: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
IfcStair (reader IFC_3)
    attributes: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
IfcTypeObject (reader IFC_3)
    attributes: ifc_type_name string, GlobalId char(22), Name string, Description string, ApplicableOccurrence string, Tag string, ElementType string, PredefinedType string
IfcWall (reader IFC_3)
    attributes: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
IfcWindow (reader IFC_3)
    attributes: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

Bookmark: Unneeded 使用しないifcクラス
IfcProject (reader IFC_2) [off]
    attributes: GlobalId char(22), Name string, Description string, ObjectType string, LongName string, Phase string
IfcSite (reader IFC_2) [off]
    attributes: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
IfcBuildingStorey (reader IFC_2) [off]
    attributes: GlobalId char(22), Name string, Description string, ObjectType string, LongName string, CompositionType enumeration, Elevation real
IfcOpeningElement (reader IFC_2) [off]
    attributes: GlobalId char(22), Name string, Description string, ObjectType string, Tag string
IfcElementAssembly (reader IFC_2) [off]
    attributes: GlobalId char(22), Name string, Description string, ObjectType string, Tag string, AssemblyPlace enumeration, PredefinedType enumeration
PropertySetDefinition (reader IFC_2) [off]
    attributes: ifc_properties{}.data_type string, ifc_properties{}.property_type string, ifc_properties{}.name string, ifc_property_set_name string
QuantitySetDefinition (reader IFC_2) [off]
    attributes: ifc_quantities{}.type string, ifc_quantity_set_name string, ifc_quantities{}.name string

Bookmark: parent/child lookupの作成
IfcPropertySet (reader IFC_1)
    attributes: BuildingAddress.PostalCode string, RefLatitude real, AssemblyPlace enumeration, SiteAddress.PostalCode string, SiteAddress.PostalBox string, RefElevation real, ElevationOfRefHeight real, Description string, SiteAddress.Description string, RefLongitude real, SiteAddress.Purpose enumeration, BuildingAddress.PostalBox string, BuildingAddress.InternalLocation string, GlobalId string, BuildingAddress.Purpose enumeration, LongName string, BuildingAddress.Country string, SiteAddress.Town string, SiteAddress.Region string, NumberOfTreads int, CompositionType enumeration, ShapeType enumeration, Phase string, LandTitleNumber string, OverallWidth real, TreadLength real, SiteAddress.Country string, SiteAddress.AddressLines string, PredefinedType enumeration, BuildingAddress.Town string,
      SiteAddress.InternalLocation string, Name string, ObjectType string, OverallHeight real, SiteAddress.UserDefinedPurpose string, BuildingAddress.Region string, BuildingAddress.AddressLines string, InteriorOrExteriorSpace enumeration, BuildingAddress.UserDefinedPurpose string, ElevationWithFlooring real, NumberOfRiser int, Tag string, ElevationOfTerrain real, Elevation real, RiserHeight real, BuildingAddress.Description string
    -> BinaryEncoder
BinaryEncoder
    ATTR_TO_ENCODE = ifc_unique_id
    DEST_ATTR = _unique_id
    ENCODING_TYPE = HEX
    -> BinaryEncoder_2
BinaryEncoder_2
    ATTR_TO_ENCODE = ifc_parent_unique_id
    DEST_ATTR = _parent_id
    ENCODING_TYPE = HEX
    -> VariableSetter
VariableSetter
    SCOPE = Global
    VALUE = @Value(_parent_id)
    VARNAME = p@Value(_unique_id)
    -> VariableSetter_2
VariableSetter_2
    SCOPE = Global
    VALUE = @Value(fme_feature_type)
    VARNAME = t@Value(_unique_id)

Bookmark: Building 建築情報
IfcBuilding (reader IFC_2)
    attributes: GlobalId char(22), Name string, Description string, ObjectType string, LongName string, CompositionType string, ElevationOfRefHeight real, ElevationOfTerrain real, BuildingAddress.Purpose enumeration, BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string
    -> GeometryRemover
Note: Remove Geometry / ジオメトリの削除
GeometryRemover
    -> AttributeRenamer_12
Note: Set gml_id / gml idのセット
AttributeRenamer_12
    ATTR_TABLE = RENAME_SET_DEFAULT ifc_unique_id > gml_id
    -> Building (writer CITYGML_1)
Building (writer CITYGML_1)

Bookmark: Room 部屋・空間
IfcSpace (reader IFC_2)
    attributes: GlobalId char(22), Name string, Description string, ObjectType string, LongName string, CompositionType enumeration, InteriorOrExteriorSpace enumeration, ElevationWithFlooring real
    -> ConvertGeometry_10
Note: Convert Geometry to / simple surface / ジオメトリを単純な面に変換
ConvertGeometry_10
    IFC_UNIQUE_ID = @Value(ifc_unique_id)
    -> AttributeRenamer_8
Note: Set gml id / gml idのセット
AttributeRenamer_8
    ATTR_TABLE = RENAME_SET_DEFAULT ifc_unique_id > gml_id
    -> GetGrandParentID_8
Note: Set parent id / parent idのセット
GetGrandParentID_8
    ATTR_TO_ENCODE = ifc_parent_unique_id
    DEST_ATTR = gml_parent_id
    -> CityGMLGeometrySetter_2
Note: Set LOD and role / LODとroleのセット
CityGMLGeometrySetter_2
    GEOM = lod4MultiSurface
    ROLE = interiorRoom
    -> Room (writer CITYGML_1)
Room (writer CITYGML_1)
    attributes: Name xml_buffer, ObjectType xml_buffer, Tag xml_buffer

Bookmark: Buildingart 建築の部分要素（基本分類に入らないifcクラスの形状モデル）
IfcFooting (reader IFC_2)
    attributes: GlobalId char(22), Name string, Description string, ObjectType string, Tag string, PredefinedType enumeration
    -> ConvertGeometry_13
Note: Convert Geometry to / simple surface / ジオメトリを単純な面に変換
ConvertGeometry_13
    IFC_UNIQUE_ID = @Value(ifc_unique_id)
    -> AttributeRenamer_11
Note: Set gml_id / gml idのセット
AttributeRenamer_11
    ATTR_TABLE:
      RENAME_SET_DEFAULT ifc_parent_unique_id > gml_parent_id
      RENAME_SET_DEFAULT ifc_unique_id > gml_id
    -> GetGrandParentID_11
Note: Set parent id / parent idのセット
GetGrandParentID_11
    ATTR_TO_ENCODE = gml_parent_id
    DEST_ATTR = gml_parent_id
    -> CityGMLGeometrySetter_8
Note: Set LOD and role / LODとroleのセット
CityGMLGeometrySetter_8
    GEOM = lod4MultiSurface
    ROLE = consistsOfBuildingPart
    -> BuildingPart (writer CITYGML_1)
BuildingPart (writer CITYGML_1)
    attributes: Name xml_char(200), ObjectType xml_char(200), Tag xml_char(200)

Bookmark: Window 窓
IfcPlate (reader IFC_2)
    attributes: GlobalId char(22), Name string, Description string, ObjectType string, Tag string
    -> ConvertGeometry_2
Note: Convert Geometry to / simple surface / ジオメトリを単純な面に変換
ConvertGeometry_2
    IFC_UNIQUE_ID = @Value(ifc_unique_id)
    -> AttributeRenamer
Note: Set gml_id / gml idのセット
AttributeRenamer
    ATTR_TABLE:
      RENAME_SET_DEFAULT ifc_parent_unique_id > gml_parent_id
      RENAME_SET_DEFAULT ifc_unique_id > gml_id
    -> CityGMLGeometrySetter_7
IfcWindow (reader IFC_2)
    attributes: GlobalId char(22), Name string, Description string, ObjectType string, Tag string, OverallHeight real, OverallWidth real
    -> ConvertGeometry_4
ConvertGeometry_4
    IFC_UNIQUE_ID = @Value(ifc_unique_id)
    -> AttributeRenamer_2
AttributeRenamer_2
    ATTR_TABLE = RENAME_SET_DEFAULT ifc_unique_id > gml_id
    -> GetGrandParentID_2
Note: Set parent id / parent idのセット
GetGrandParentID_2
    ATTR_TO_ENCODE = ifc_parent_unique_id
    DEST_ATTR = gml_parent_id
    -> CityGMLGeometrySetter_7
Note: Set LOD and role / LODとroleのセット
CityGMLGeometrySetter_7
    GEOM = lod4MultiSurface
    ROLE = opening
    -> Window (writer CITYGML_1)
Window (writer CITYGML_1)
    attributes: Name xml_char(200), ObjectType xml_char(200), Tag xml_char(200)

Bookmark: IntBuildingInstallation 設備・機械等
IfcFlowTerminal (reader IFC_2)
    attributes: GlobalId char(22), Name string, Description string, ObjectType string, Tag string
    -> ConvertGeometry_12
Note: Convert Geometry to / simple surface / ジオメトリを単純な面に変換
ConvertGeometry_12
    IFC_UNIQUE_ID = @Value(ifc_unique_id)
    -> BinaryEncoder_10
Note: Get parent type / parent typeの取得
BinaryEncoder_10
    ATTR_TO_ENCODE = ifc_parent_unique_id
    DEST_ATTR = _parent_id
    ENCODING_TYPE = HEX
    -> VariableRetriever_9
VariableRetriever_9
    SCOPE = Global
    VALUE_ATTR = _parent_type
    VARNAME = t@Value(_parent_id)
    -> AttributeRenamer_10
Note: Set gml_id / gml idのセット
AttributeRenamer_10
    ATTR_TABLE:
      RENAME_SET_DEFAULT ifc_parent_unique_id > gml_parent_id
      RENAME_SET_DEFAULT ifc_unique_id > gml_id
    -> Tester_7
Note: Separate room items / from building items
Tester_7
    BOOL_OP = OR
    TEST_CLAUSE = TEST @Value(_parent_type) = IfcSpace
    TEST_MODE = TEST
    PASSED -> CityGMLGeometrySetter_11
    FAILED -> GetGrandParentID_10
Note: Set LOD and role / LODとroleのセット
CityGMLGeometrySetter_11
    GEOM = lod4Geometry
    ROLE = roomInstallation
    -> IntBuildingInstallation (writer CITYGML_1)
Note: Set parent id / parent idのセット
GetGrandParentID_10
    ATTR_TO_ENCODE = gml_parent_id
    DEST_ATTR = gml_parent_id
    -> CityGMLGeometrySetter_12
CityGMLGeometrySetter_12
    GEOM = lod4Geometry
    ROLE = interiorBuildingInstallation
    -> IntBuildingInstallation (writer CITYGML_1)
IntBuildingInstallation (writer CITYGML_1)
    attributes: Name xml_buffer, ObjectType xml_buffer, Tag xml_buffer

Bookmark: BuildingFurniture 家具
IfcBuildingElementProxy (reader IFC_2)
    attributes: GlobalId char(22), Name string, Description string, ObjectType string, Tag string, CompositionType enumeration
    -> ConvertGeometry_11
IfcFurnishingElement (reader IFC_2)
    attributes: GlobalId char(22), Name string, Description string, ObjectType string, Tag string
    -> ConvertGeometry_11
Note: Convert Geometry to / simple surface / ジオメトリを単純な面に変換
ConvertGeometry_11
    IFC_UNIQUE_ID = @Value(ifc_unique_id)
    -> BinaryEncoder_9
Note: Get parent type / parent typeの取得
BinaryEncoder_9
    ATTR_TO_ENCODE = ifc_parent_unique_id
    DEST_ATTR = _parent_id
    ENCODING_TYPE = HEX
    -> VariableRetriever_8
VariableRetriever_8
    SCOPE = Global
    VALUE_ATTR = _parent_type
    VARNAME = t@Value(_parent_id)
    -> AttributeRenamer_9
Note: Set gml_id / gml idのセット
AttributeRenamer_9
    ATTR_TABLE:
      RENAME_SET_DEFAULT ifc_parent_unique_id > gml_parent_id
      RENAME_SET_DEFAULT ifc_unique_id > gml_id
    -> Tester_6
Note: Separate room items / from building items
Tester_6
    BOOL_OP = OR
    TEST_CLAUSE = TEST @Value(_parent_type) = IfcSpace
    TEST_MODE = TEST
    PASSED -> CityGMLGeometrySetter_3
    FAILED -> GetGrandParentID_9
Note: Set parent id / parent idのセット
GetGrandParentID_9
    ATTR_TO_ENCODE = gml_parent_id
    DEST_ATTR = gml_parent_id
    -> CityGMLGeometrySetter_3
Note: Set LOD and role / LODとroleのセット
CityGMLGeometrySetter_3
    GEOM = lod4Geometry
    ROLE = boundedBy
    -> BuildingFurniture (writer CITYGML_1)
BuildingFurniture (writer CITYGML_1)
    attributes: Name xml_buffer, ObjectType xml_buffer, Tag xml_buffer

Bookmark: Door 扉
IfcDoor (reader IFC_2)
    attributes: GlobalId char(22), Name string, Description string, ObjectType string, Tag string, OverallHeight real, OverallWidth real
    -> ConvertGeometry_5
Note: Convert Geometry to / simple surface / ジオメトリを単純な面に変換
ConvertGeometry_5
    IFC_UNIQUE_ID = @Value(ifc_unique_id)
    -> BinaryEncoder_4
Note: Get parent type / parent typeの取得
BinaryEncoder_4
    ATTR_TO_ENCODE = ifc_parent_unique_id
    DEST_ATTR = _parent_id
    ENCODING_TYPE = HEX
    -> VariableRetriever_3
VariableRetriever_3
    SCOPE = Global
    VALUE_ATTR = _parent_type
    VARNAME = t@Value(_parent_id)
    -> AttributeRenamer_13
Note: Set gml_id / gml idのセット
AttributeRenamer_13
    ATTR_TABLE:
      RENAME_SET_DEFAULT ifc_parent_unique_id > gml_parent_id
      RENAME_SET_DEFAULT ifc_unique_id > gml_id
    -> Tester_2
Note: Separate wall doors from / curtain wall doors
Tester_2
    BOOL_OP = OR
    TEST_CLAUSE = TEST @Value(_parent_type) NOT_= IfcCurtainWall
    TEST_MODE = TEST
    PASSED -> GetGrandParentID
    FAILED -> CityGMLGeometrySetter_6
Note: Set parent id / parent idのセット
GetGrandParentID
    ATTR_TO_ENCODE = gml_parent_id
    DEST_ATTR = gml_parent_id
    -> CityGMLGeometrySetter_6
Note: Set LOD and role / LODとroleのセット
CityGMLGeometrySetter_6
    GEOM = lod4MultiSurface
    ROLE = opening
    -> Door (writer CITYGML_1)
Door (writer CITYGML_1)
    attributes: Name xml_char(200), ObjectType xml_char(200), Tag xml_char(200)

Bookmark: Roof and Floor 屋根・床
IfcRoof (reader IFC_2)
    attributes: GlobalId char(22), Name string, Description string, ObjectType string, Tag string, ShapeType enumeration
    -> AttributeRenamer_7
Note: Set gml_id / gml idのセット
AttributeRenamer_7
    ATTR_TABLE = RENAME_SET_DEFAULT ifc_unique_id > gml_id
    -> FeatureMerger_2 [REQUESTOR]
IfcSlab (reader IFC_2)
    attributes: GlobalId char(22), Name string, Description string, ObjectType string, Tag string, PredefinedType enumeration
    -> ConvertGeometry_6
Note: Convert Geometry to / simple surface / ジオメトリを単純な面に変換
ConvertGeometry_6
    IFC_UNIQUE_ID = @Value(ifc_unique_id)
    -> BinaryEncoder_5
Note: Get parent type / parent typeの取得
BinaryEncoder_5
    ATTR_TO_ENCODE = ifc_parent_unique_id
    DEST_ATTR = _parent_id
    ENCODING_TYPE = HEX
    -> VariableRetriever_4
VariableRetriever_4
    SCOPE = Global
    VALUE_ATTR = _parent_type
    VARNAME = t@Value(_parent_id)
    -> AttributeFilter
Note: Routeto appropriate parent / parentのルートの適正化
AttributeFilter
    ATTR_NAME = _parent_type
    ATTR_VALUES = <Empty>,<Missing>,<Null>,<Unfiltered>,IfcRoof,IfcStair
    <UNFILTERED> -> AttributeRenamer_6
    IfcRoof -> FeatureMerger_2 [SUPPLIER]
    IfcStair -> FeatureMerger_3 [SUPPLIER]
Note: Add roof slab geometry onto roof / 屋根スラブ形状を屋根に追加
FeatureMerger_2
    JOIN_KEYS = @Value(gml_id) @Value(ifc_parent_unique_id) AUTO
    MERGE_TYPE = Geometry
    PROCESS_DUPS = NO
    REJECT_NULL_MISSING_KEYS = No
    SUPPLIERS_FIRST = No
    MERGED -> GetGrandParentID_5
Note: Set parent id / parent idのセット
GetGrandParentID_5
    ATTR_TO_ENCODE = ifc_parent_unique_id
    DEST_ATTR = gml_parent_id
    -> CityGMLGeometrySetter
Note: Set LOD and role / LODとroleのセット
CityGMLGeometrySetter
    GEOM = lod4MultiSurface
    ROLE = boundedBy
    -> RoofSurface (writer CITYGML_1)
RoofSurface (writer CITYGML_1)
    attributes: Name xml_char(200), ObjectType xml_char(200), Tag xml_char(200)
Note: Set gml_id / gml idのセット
AttributeRenamer_6
    ATTR_TABLE = RENAME_SET_DEFAULT ifc_unique_id > gml_id
    -> GetGrandParentID_4
Note: Set parent id / parent idのセット
GetGrandParentID_4
    ATTR_TO_ENCODE = ifc_parent_unique_id
    DEST_ATTR = gml_parent_id
    -> CityGMLGeometrySetter_4
Note: Set LOD and role / LODとroleのセット
CityGMLGeometrySetter_4
    GEOM = lod4MultiSurface
    ROLE = boundedBy
    -> FloorSurface (writer CITYGML_1)
FloorSurface (writer CITYGML_1)
    attributes: Name xml_char(200), ObjectType xml_char(200), Tag xml_char(200)

Bookmark: BuildingInstallation 構造要素、階段要素
IfcColumn (reader IFC_2)
    attributes: GlobalId char(22), Name string, Description string, ObjectType string, Tag string
    -> ConvertGeometry_7
IfcBeam (reader IFC_2)
    attributes: GlobalId char(22), Name string, Description string, ObjectType string, Tag string
    -> ConvertGeometry_7
Note: Convert Geometry to / simple surface / ジオメトリを単純な面に変換
ConvertGeometry_7
    IFC_UNIQUE_ID = @Value(ifc_unique_id)
    -> BinaryEncoder_6
Note: Get parent type / parent typeの取得
BinaryEncoder_6
    ATTR_TO_ENCODE = ifc_parent_unique_id
    DEST_ATTR = _parent_id
    ENCODING_TYPE = HEX
    -> VariableRetriever_5
VariableRetriever_5
    SCOPE = Global
    VALUE_ATTR = _parent_type
    VARNAME = t@Value(_parent_id)
    -> Tester_4
IfcRailing (reader IFC_2)
    attributes: GlobalId char(22), Name string, Description string, ObjectType string, Tag string, PredefinedType enumeration
    -> ConvertGeometry_8
ConvertGeometry_8
    IFC_UNIQUE_ID = @Value(ifc_unique_id)
    -> BinaryEncoder_7
BinaryEncoder_7
    ATTR_TO_ENCODE = ifc_parent_unique_id
    DEST_ATTR = _parent_id
    ENCODING_TYPE = HEX
    -> VariableRetriever_6
VariableRetriever_6
    SCOPE = Global
    VALUE_ATTR = _parent_type
    VARNAME = t@Value(_parent_id)
    -> Tester_5
Note: Separate stair railings / from builiding railings / 階段の手すりと建物の手すりを分類
Tester_5
    BOOL_OP = OR
    TEST_CLAUSE = TEST @Value(_parent_type) = IfcStair
    TEST_MODE = TEST
    PASSED -> FeatureMerger_3 [SUPPLIER]
    FAILED -> Tester_4
Tester_4
    BOOL_OP = OR
    TEST_CLAUSE = TEST @Value(_parent_type) = IfcElementAssembly
    TEST_MODE = TEST
    PASSED -> GetGrandParentID_6
    FAILED -> AttributeRenamer_3
Note: Get interim parent / interim parentの取得
GetGrandParentID_6
    ATTR_TO_ENCODE = ifc_parent_unique_id
    DEST_ATTR = gml_parent_id
    -> AttributeRenamer_3
IfcStairFlight (reader IFC_2)
    attributes: GlobalId char(22), Name string, Description string, ObjectType string, Tag string, NumberOfRiser int, NumberOfTreads int, RiserHeight real, TreadLength real
    -> ConvertGeometry_9
ConvertGeometry_9
    IFC_UNIQUE_ID = @Value(ifc_unique_id)
    -> FeatureMerger_3 [SUPPLIER]
Note: Add part geometry to Stair / 階段に部分的な形状の追加
IfcStair (reader IFC_2)
    attributes: GlobalId char(22), Name string, Description string, ObjectType string, Tag string, ShapeType enumeration
    -> ConvertGeometry_15
ConvertGeometry_15
    IFC_UNIQUE_ID = @Value(ifc_unique_id)
    -> FeatureMerger_3 [REQUESTOR]
FeatureMerger_3
    GEOM_TYPE = Build Aggregates
    JOIN_KEYS = @Value(ifc_unique_id) @Value(ifc_parent_unique_id) AUTO
    MERGE_TYPE = Geometry
    PROCESS_DUPS = YES
    REJECT_NULL_MISSING_KEYS = No
    SUPPLIERS_FIRST = No
    MERGED -> BinaryEncoder_8
Note: Get parent type / parent typeの取得
BinaryEncoder_8
    ATTR_TO_ENCODE = ifc_parent_unique_id
    DEST_ATTR = _parent_id
    ENCODING_TYPE = HEX
    -> VariableRetriever_7
VariableRetriever_7
    SCOPE = Global
    VALUE_ATTR = _parent_type
    VARNAME = t@Value(_parent_id)
    -> AttributeRenamer_3
Note: Set gml_id / gml idのセット
AttributeRenamer_3
    ATTR_TABLE = RENAME_SET_DEFAULT ifc_unique_id > gml_id
    -> GetGrandParentID_7
Note: Set parent id / parent idのセット
GetGrandParentID_7
    ATTR_TO_ENCODE = gml_parent_id
    DEST_ATTR = gml_parent_id
    -> CityGMLGeometrySetter_10
Note: Set LOD and role / LODとroleのセット
CityGMLGeometrySetter_10
    GEOM = lod4Geometry
    ROLE = interiorBuildingInstallation
    -> BuildingInstallation (writer CITYGML_1)
BuildingInstallation (writer CITYGML_1)
    attributes: Name xml_buffer, ObjectType xml_buffer, Tag xml_buffer

Bookmark: WallSurface 壁・カーテンウォール
IfcMember (reader IFC_2)
    attributes: GlobalId char(22), Name string, Description string, ObjectType string, Tag string
    -> BinaryEncoder_3
Note: Get parent type / parent typeの取得
BinaryEncoder_3
    ATTR_TO_ENCODE = ifc_parent_unique_id
    DEST_ATTR = _parent_id
    ENCODING_TYPE = HEX
    -> VariableRetriever_2
VariableRetriever_2
    SCOPE = Global
    VALUE_ATTR = _parent_type
    VARNAME = t@Value(_parent_id)
    -> Tester
Note: Separate curtain wall memebrs / from Stair members / 階段メンバとカーテンウォールメンバを分類
Tester
    BOOL_OP = OR
    TEST_CLAUSE = TEST @Value(_parent_type) = IfcCurtainWall
    TEST_MODE = TEST
    PASSED -> FeatureMerger [SUPPLIER]
    FAILED -> ConvertGeometry_3
ConvertGeometry_3
    IFC_UNIQUE_ID = @Value(ifc_unique_id)
    -> FeatureMerger_3 [SUPPLIER]
IfcWallStandardCase (reader IFC_2)
    attributes: GlobalId char(22), Name string, Description string, ObjectType string, Tag string
    -> ConvertGeometry
IfcWall (reader IFC_2)
    attributes: GlobalId char(22), Name string, Description string, ObjectType string, Tag string
    -> ConvertGeometry
ConvertGeometry
    IFC_UNIQUE_ID = @Value(ifc_unique_id)
    -> AttributeRenamer_4
Note: Add member geometry to curtain wal / カーテンウォールにメンバ形状を追加l
IfcCurtainWall (reader IFC_2)
    attributes: GlobalId char(22), Name string, Description string, ObjectType string, Tag string
    -> FeatureMerger [REQUESTOR]
FeatureMerger
    GEOM_TYPE = Build Aggregates
    JOIN_KEYS = @Value(ifc_unique_id) @Value(ifc_parent_unique_id) AUTO
    MERGE_TYPE = Geometry
    PROCESS_DUPS = YES
    REJECT_NULL_MISSING_KEYS = No
    SUPPLIERS_FIRST = No
    UNMERGED_REQUESTOR -> ConvertGeometry_14
ConvertGeometry_14
    IFC_UNIQUE_ID = @Value(ifc_unique_id)
    -> AttributeRenamer_4
Note: Set gml_id / gml idのセット
AttributeRenamer_4
    ATTR_TABLE = RENAME_SET_DEFAULT ifc_unique_id > gml_id
    -> GetGrandParentID_3
Note: Set gml_id / gml idのセット
GetGrandParentID_3
    ATTR_TO_ENCODE = ifc_parent_unique_id
    DEST_ATTR = gml_parent_id
    -> CityGMLGeometrySetter_5
Note: Set LOD and role / LODとroleのセット
CityGMLGeometrySetter_5
    GEOM = lod4MultiSurface
    ROLE = boundedBy
    -> WallSurface (writer CITYGML_1)
WallSurface (writer CITYGML_1)
    attributes: Name xml_char(200), ObjectType xml_char(200), Tag xml_char(200)

FME custom transformer ConvertGeometry

Parameters:
- IFC_UNIQUE_ID = @Value(ifc_unique_id)   # Ifc Unique Id

Input (input)
    -> GeometryPartExtractor_3
GeometryPartExtractor_3
    GQUERY:
      for $geom in //geometry
      where $geom/@fme_geometry_name = 'Body'
      return number($geom/@fme_id)
    EXTRACTED -> GeometryCoercer_3
GeometryCoercer_3
    GQUERY:
      for $geom in //geometry
      where $geom/@fme_geometry_type = 'IFMEExtrusion'
      or $geom/@fme_geometry_type = 'IFMEBRepSolid'
      return number($geom/@fme_id)
    KIND = fme_composite_surface
    COERCED -> Deaggregator
    UNTOUCHED -> Deaggregator
Deaggregator
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten All Levels
    SPLIT_COMPOSITES = No
    DEAGGREGATED -> Aggregator
Aggregator
    ACCUM_ATTRS_NAME = Merge Incoming Attributes
    AGGREGATE_TYPE = Homogeneous Collection (If Possible)
    GROUP_BY = ifc_unique_id
    MODE = Geometry - Assemble One Level
    ORDERED = Yes
    SEP = ,
    AGGREGATE -> GeometryRefiner_3
GeometryRefiner_3
    -> Output (output)
Output (output)

FME custom transformer GetGrandParentID

Parameters:
- ATTR_TO_ENCODE =   # "" Source ID
- DEST_ATTR = gml_parent_id   # TYPE:varchar(200) Destination Attribute

Input (input)
    -> BinaryEncoder_3
BinaryEncoder_3
    ATTR_TO_ENCODE = $(ATTR_TO_ENCODE)
    DEST_ATTR = _parent_id
    ENCODING_TYPE = HEX
    -> VariableRetriever_5
VariableRetriever_5
    SCOPE = Global
    VALUE_ATTR = _gparent_id
    VARNAME = p@Value(_parent_id)
    -> BinaryDecoder
BinaryDecoder
    ATTR_ENCODING = utf-8
    ATTR_TO_DECODE = _gparent_id
    DEST_ATTR = $(DEST_ATTR)
    ENCODING_TYPE = HEX
    -> Output (output)
Output (output)

FME custom transformer CityGMLGeometrySetter

Parameters:
- GEOM =   # CityGML Lod Name
- ROLE =   # Feature Role

INPUT (input)
    -> AttributeCreator
AttributeCreator
    ATTR_TABLE:
      SET_TO citygml_lod_name = $(GEOM)
      SET_TO citygml_feature_role = $(ROLE)
    -> GeometryPropertySetter
GeometryPropertySetter
    OVERWRITE_CHOICE = Yes
    REMOVE_ATTRIBUTE = No
    SETTYPE_PARAM = Traits From Attributes
    SRC_ATTRS = citygml_lod_name
    SET -> OUTPUT (output)
OUTPUT (output)
